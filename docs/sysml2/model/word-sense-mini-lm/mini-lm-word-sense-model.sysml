package WordSense {
    part def MiniLMWordSenseModel {
        doc /* Runs the quantized MiniLM transformer with ONNX Runtime and returns pooled contextual vectors of target words. */

        comment sourceRef /* Source: src/DemaConsulting.WordSense.MiniLM/MiniLMWordSenseModel.cs */
        comment testRef /* Test: test/DemaConsulting.WordSense.MiniLM.Tests/MiniLMWordSenseModelTests.cs */
        comment designRef /* Design: docs/design/word-sense-mini-lm/mini-lm-word-sense-model.md */
        comment verificationRef /* Verification: docs/verification/word-sense-mini-lm/mini-lm-word-sense-model.md */
        comment reqRef /* Requirements: docs/reqstream/word-sense-mini-lm/mini-lm-word-sense-model.yaml */
    }
}
