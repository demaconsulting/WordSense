package WordSense {
    part def DownloadMirror {
        doc /* Validated configuration of a user-supplied download mirror, from options or environment variables. */

        comment sourceRef /* Source: src/DemaConsulting.WordSense.MiniLM/DownloadMirror.cs */
        comment testRef /* Test: test/DemaConsulting.WordSense.MiniLM.Tests/DownloadMirrorTests.cs */
        comment designRef /* Design: docs/design/word-sense-mini-lm/download-mirror.md */
        comment verificationRef /* Verification: docs/verification/word-sense-mini-lm/download-mirror.md */
        comment reqRef /* Requirements: docs/reqstream/word-sense-mini-lm/download-mirror.yaml */
    }
}
