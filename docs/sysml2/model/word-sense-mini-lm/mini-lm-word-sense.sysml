package WordSense {
    part def MiniLMWordSense {
        doc /* The convenience factory that ensures the model files, loads the embedded weights table trained for the model and returns a classifier wired to the MiniLM encoder. */

        comment sourceRef /* Source: src/DemaConsulting.WordSense.MiniLM/MiniLMWordSense.cs, src/DemaConsulting.WordSense.MiniLM/MiniLMWordSenseOptions.cs */
        comment testRef /* Test: test/DemaConsulting.WordSense.MiniLM.Tests/WordSenseTests.cs */
        comment designRef /* Design: docs/design/word-sense-mini-lm/mini-lm-word-sense.md */
        comment verificationRef /* Verification: docs/verification/word-sense-mini-lm/mini-lm-word-sense.md */
        comment reqRef /* Requirements: docs/reqstream/word-sense-mini-lm/mini-lm-word-sense.yaml */
    }
}
