package WordSense {
    part def WordSenseModelDownloader {
        doc /* Fetches and verifies the files of a model from the mirror, Hugging Face and GitHub LFS in order. */

        comment sourceRef /* Source: src/DemaConsulting.WordSense.MiniLM/WordSenseModelDownloader.cs, src/DemaConsulting.WordSense.MiniLM/WordSenseModelDownloaderOptions.cs (also declares WordSenseModelDownloadProgress and WordSenseModelDownloadException), src/DemaConsulting.WordSense.MiniLM/WordSenseModelLocation.cs, src/DemaConsulting.WordSense.MiniLM/WordSenseModelCatalog.cs */
        comment testRef /* Test: test/DemaConsulting.WordSense.MiniLM.Tests/WordSenseModelDownloaderTests.cs */
        comment designRef /* Design: docs/design/word-sense-mini-lm/word-sense-model-downloader.md */
        comment verificationRef /* Verification: docs/verification/word-sense-mini-lm/word-sense-model-downloader.md */
        comment reqRef /* Requirements: docs/reqstream/word-sense-mini-lm/word-sense-model-downloader.yaml */
    }
}
