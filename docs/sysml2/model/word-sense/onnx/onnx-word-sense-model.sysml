package WordSense {
    part def OnnxWordSenseModel {
        doc /* The public abstract base of the encoder models, usable on its own and implementing IDownloadableWordSenseModel and the internal part-of-speech evidence marker: it makes the model files available and verified, opens the ONNX encoder and embedded weights on first use, and classifies (ensuring the files lazily when a word needs the encoder: a word with scored senses or, for a model that uses its head, a known word of several parts of speech or, for a model that uses its tense head, a same-spelling verb), loads and checks the embedded part-of-speech head with the weights whenever its description names one, reporting its failures as the typed core exceptions (ModelUnavailableException, ModelIntegrityException, DownloadConfigurationException); it references only the core package, and disposing it releases the encoder and cancels a download in flight. */

        comment sourceRef /* Source: src/DemaConsulting.WordSense.Onnx/OnnxWordSenseModel.cs */
        comment testRef /* Test: test/DemaConsulting.WordSense.Onnx.Tests/OnnxWordSenseModelTests.cs */
        comment designRef /* Design: docs/design/word-sense/onnx/onnx-word-sense-model.md */
        comment verificationRef /* Verification: docs/verification/word-sense/onnx/onnx-word-sense-model.md */
        comment reqRef /* Requirements: docs/reqstream/word-sense/onnx/onnx-word-sense-model.yaml */
    }
}
