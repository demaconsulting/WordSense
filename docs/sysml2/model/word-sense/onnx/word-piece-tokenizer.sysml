package WordSense {
    part def WordPieceTokenizer {
        doc /* A managed BERT WordPiece tokenizer, uncased or cased, that records which tokens belong to each word. */

        comment sourceRef /* Source: src/DemaConsulting.WordSense.Onnx/WordPieceTokenizer.cs, src/DemaConsulting.WordSense.Onnx/TokenizedText.cs */
        comment testRef /* Test: test/DemaConsulting.WordSense.Onnx.Tests/WordPieceTokenizerTests.cs */
        comment designRef /* Design: docs/design/word-sense/onnx/word-piece-tokenizer.md */
        comment verificationRef /* Verification: docs/verification/word-sense/onnx/word-piece-tokenizer.md */
        comment reqRef /* Requirements: docs/reqstream/word-sense/onnx/word-piece-tokenizer.yaml */
    }
}
