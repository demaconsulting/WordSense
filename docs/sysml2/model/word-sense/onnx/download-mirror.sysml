package WordSense {
    part def DownloadMirror {
        doc /* Validated configuration of a user-supplied download mirror, built from download options or from environment variables. */

        comment sourceRef /* Source: src/DemaConsulting.WordSense.Onnx/DownloadMirror.cs */
        comment testRef /* Test: test/DemaConsulting.WordSense.Onnx.Tests/DownloadMirrorTests.cs */
        comment designRef /* Design: docs/design/word-sense/onnx/download-mirror.md */
        comment verificationRef /* Verification: docs/verification/word-sense/onnx/download-mirror.md */
        comment reqRef /* Requirements: docs/reqstream/word-sense/onnx/download-mirror.yaml */
    }
}
