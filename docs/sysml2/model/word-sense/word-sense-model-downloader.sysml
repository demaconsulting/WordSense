package WordSense {
    part def WordSenseModelDownloader {
        doc /* Fetches and verifies the model files from the mirror, Hugging Face and GitHub LFS in order. */

        comment sourceRef /* Source: src/DemaConsulting.WordSense/WordSenseModelDownloader.cs, src/DemaConsulting.WordSense/WordSenseModelDownloaderOptions.cs (also declares WordSenseModelDownloadProgress and WordSenseModelDownloadException), src/DemaConsulting.WordSense/WordSenseModelLocation.cs, src/DemaConsulting.WordSense/WordSenseModelCatalog.cs */
        comment testRef /* Test: test/DemaConsulting.WordSense.Tests/WordSenseModelDownloaderTests.cs */
        comment designRef /* Design: docs/design/word-sense/word-sense-model-downloader.md */
        comment verificationRef /* Verification: docs/verification/word-sense/word-sense-model-downloader.md */
        comment reqRef /* Requirements: docs/reqstream/word-sense/word-sense-model-downloader.yaml */
    }
}
