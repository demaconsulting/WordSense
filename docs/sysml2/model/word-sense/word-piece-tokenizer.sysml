package WordSense {
    part def WordPieceTokenizer {
        doc /* Splits text into BERT uncased word pieces with character offsets and builds model input windows. */

        comment sourceRef /* Source: src/DemaConsulting.WordSense/WordPieceTokenizer.cs, src/DemaConsulting.WordSense/TokenizedText.cs */
        comment testRef /* Test: test/DemaConsulting.WordSense.Tests/WordPieceTokenizerTests.cs */
        comment designRef /* Design: docs/design/word-sense/word-piece-tokenizer.md */
        comment verificationRef /* Verification: docs/verification/word-sense/word-piece-tokenizer.md */
        comment reqRef /* Requirements: docs/reqstream/word-sense/word-piece-tokenizer.yaml */
    }
}
