package WordSense {
    part def FormAuditor {
        doc /* Repeatable quality gate of the generated forms: a seeded stratified sample checked against an independent checker, reported per stratum with a Wilson confidence interval. */

        comment sourceRef /* Source: tools/WordSense.Builder/Data/FormAuditor.cs */
        comment testRef /* Test: test/WordSense.Builder.Tests/Data/FormAuditorTests.cs */
        comment designRef /* Design: docs/design/word-sense/word-data/form-auditor.md */
        comment verificationRef /* Verification: docs/verification/word-sense/word-data/form-auditor.md */
        comment reqRef /* Requirements: docs/reqstream/word-sense/word-data/form-auditor.yaml */
    }
}
