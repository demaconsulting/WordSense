package WordSense {
    part def Demo {
        doc /* Demonstration greeting class showing how a DEMA Consulting .NET library class should be structured, documented, and tested. */

        comment sourceRef /* Source: src/DemaConsulting.WordSense/Demo.cs */
        comment testRef /* Test: test/DemaConsulting.WordSense.Tests/DemoTests.cs */
        comment designRef /* Design: docs/design/word-sense/demo.md */
        comment verificationRef /* Verification: docs/verification/word-sense/demo.md */
        comment reqRef /* Requirements: docs/reqstream/word-sense/demo.yaml */
    }
}
