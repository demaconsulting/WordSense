package WordSense {
    part def BasicWordSenseModel {
        doc /* The public statistical word-sense model: it needs no files, performs no download and classifies with the basic classifier; its disposal only marks the model so that later use throws. */

        comment sourceRef /* Source: src/DemaConsulting.WordSense.Basic/BasicWordSenseModel.cs */
        comment testRef /* Test: test/DemaConsulting.WordSense.Basic.Tests/BasicWordSenseModelTests.cs */
        comment designRef /* Design: docs/design/word-sense/basic/basic-word-sense-model.md */
        comment verificationRef /* Verification: docs/verification/word-sense/basic/basic-word-sense-model.md */
        comment reqRef /* Requirements: docs/reqstream/word-sense/basic/basic-word-sense-model.yaml */
    }
}
