package WordSense {
    part def PosTagger {
        doc /* The part-of-speech tagger of the basic model: a sparse forward-backward second-order hidden Markov model giving per-word part-of-speech posteriors for a sentence segment. */

        comment sourceRef /* Source: src/DemaConsulting.WordSense.Basic/PosTagger.cs, src/DemaConsulting.WordSense.Basic/PosTag.cs */
        comment testRef /* Test: test/DemaConsulting.WordSense.Basic.Tests/PosTaggerTests.cs */
        comment designRef /* Design: docs/design/word-sense/basic/pos-tagger.md */
        comment verificationRef /* Verification: docs/verification/word-sense/basic/pos-tagger.md */
        comment reqRef /* Requirements: docs/reqstream/word-sense/basic/pos-tagger.yaml */
    }
}
