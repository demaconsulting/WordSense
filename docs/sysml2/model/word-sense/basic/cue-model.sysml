package WordSense {
    part def CueModel {
        doc /* The context-cue model of the basic model: extracts context features around a target word and scores the candidate analyses of a form with hashed naive-Bayes weights. */

        comment sourceRef /* Source: src/DemaConsulting.WordSense.Basic/CueModel.cs */
        comment testRef /* Test: test/DemaConsulting.WordSense.Basic.Tests/CueModelTests.cs */
        comment designRef /* Design: docs/design/word-sense/basic/cue-model.md */
        comment verificationRef /* Verification: docs/verification/word-sense/basic/cue-model.md */
        comment reqRef /* Requirements: docs/reqstream/word-sense/basic/cue-model.yaml */
    }
}
