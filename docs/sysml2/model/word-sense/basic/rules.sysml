package WordSense {
    part def Rules {
        doc /* The ordered hand-written rules of the basic model: closed-class word lists and neighbor part-of-speech tests, each rule with a fixed confidence. */

        comment sourceRef /* Source: src/DemaConsulting.WordSense.Basic/Rules.cs */
        comment testRef /* Test: test/DemaConsulting.WordSense.Basic.Tests/RulesTests.cs */
        comment designRef /* Design: docs/design/word-sense/basic/rules.md */
        comment verificationRef /* Verification: docs/verification/word-sense/basic/rules.md */
        comment reqRef /* Requirements: docs/reqstream/word-sense/basic/rules.yaml */
    }
}
