package WordSense {
    part def OnnxWordSenseEncoder {
        doc /* Runs the quantized transformer model with ONNX Runtime and returns per-token hidden states. */

        comment sourceRef /* Source: src/DemaConsulting.WordSense/OnnxWordSenseEncoder.cs, src/DemaConsulting.WordSense/IWordSenseEncoder.cs */
        comment testRef /* Test: test/DemaConsulting.WordSense.Tests/OnnxWordSenseEncoderTests.cs */
        comment designRef /* Design: docs/design/word-sense/onnx-word-sense-encoder.md */
        comment verificationRef /* Verification: docs/verification/word-sense/onnx-word-sense-encoder.md */
        comment reqRef /* Requirements: docs/reqstream/word-sense/onnx-word-sense-encoder.yaml */
    }
}
