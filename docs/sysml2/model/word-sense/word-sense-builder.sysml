package WordSense {
    part def WordSenseBuilder {
        doc /* Non-shipped build-time tool that derives the dictionary word list from the pinned Moby list, compiles the embedded word lexicon and sense catalog from the data with the generated inflected forms of every dictionary word, measures the token coverage of the lexicon on plain-text files, reports the per-sense quota of the corpus, trains the fine-sense weights of each encoder model (correcting their scores to the usage of the senses with the WordNet 3.0 counts) and chooses the per-lemma thresholds by cross-validation, counts tag statistics of the open part-of-speech corpus, trains, tunes and measures the statistical basic model (including the tense of the verbs whose past and non-past share a spelling), measures the shipped models at each answer level on the held-out sentences, on SemCor, on running text and on the independent all-words gold set of untrained polysemous lemmas (drawn from the open corpus and labeled blind by two labelers, the measurement of the usage prior that SemCor cannot make) and on a second, document-disjoint all-words gold set (new public-domain documents sampled by stratum before labeling, labeled by two language models and an adjudicator, with a paired comparison of the models), and generates the senses appendix of the user guide (with every analysis of the forms of a lemma, the explanation of the keys and the heteronym section), writes every word key of the lexicon as a sorted text file, derives the heteronyms (the spellings whose key, not the spelling, decides the word) from the pronunciations of the data and a curated table and writes them as a TSV, and bounds the difference between CPUs of an int8 encoder (the CPU canary of the answers of a model and the preflight of weights and heads, which also write the weights format that records the encoder and the layout of the sense feature). */

        comment sourceRef /* Source: tools/WordSense.Builder/ (every C# file of the builder project, for example Program.cs, Corpus.cs, ChooserCorpus.cs, SenseInventory.cs, AnalysisKey.cs, CoverageReport.cs, LexiconImporter.cs, ModelTrainer.cs, EmbeddingCache.cs, CachingEncoder.cs, FitCache.cs, WeightsTrainer.cs, LogisticTrainer.cs, KernelBasis.cs, LemmaFitter.cs, Thresholds.cs, SensePrior.cs, PrecisionGate.cs, Tiers.cs, Evaluator.cs, ModelTable.cs, SemCor.cs, SenseEvaluator.cs, RunningTextEvaluator.cs, TenseEvaluator.cs, Suite.cs, SuiteEvaluator.cs, ShapeProbe.cs, ShapeProbeEvaluator.cs, Leakage.cs, Program.Evaluation.cs, OpenCorpus.cs, TaggerCounts.cs, TaggerEvaluator.cs, BasicHyperparameters.cs, BasicTrainer.cs, BasicTablesWriter.cs, BasicTuner.cs, NounVerbStacker.cs, BasicModelBuilder.cs, CueRunningReliability.cs, AppendixGenerator.cs, KeyExport.cs, Heteronyms.cs, AllWordsGold.cs, AllWordsEvaluator.cs, Gold2.cs, Gold2Sampler.cs, Gold2Labeling.cs, Gold2Evaluator.cs, Gold2Power.cs, Program.Gold2.cs and Program.FetchModels.cs), corpus/ (anchor and holdout sentences of the fine-sense corpus and the form-chooser rows with their provenance, the open part-of-speech corpus and its tag counts, the all-words gold set allwords/ and the second all-words gold set allwords/v2, the suite, the shape probe set shapes/, lexicon, the curated heteronym table curation/heteronyms.tsv) */
        comment testRef /* Test: test/WordSense.Builder.Tests/ProgramTests.cs, test/WordSense.Builder.Tests/ImageTests.cs, test/WordSense.Builder.Tests/WeightsBlobWriterTests.cs, test/WordSense.Builder.Tests/WeightsBlobWsx4Tests.cs, test/WordSense.Builder.Tests/EmbeddingCacheStreamTests.cs, test/WordSense.Builder.Tests/CanaryTests.cs, test/WordSense.Builder.Tests/TaggerCountsTests.cs, test/WordSense.Builder.Tests/OpenCorpusTests.cs, test/WordSense.Builder.Tests/TaggerEvaluatorTests.cs, test/WordSense.Builder.Tests/CorpusLicenseTests.cs, test/WordSense.Builder.Tests/BasicTrainerTests.cs, test/WordSense.Builder.Tests/CueRunningReliabilityTests.cs, test/WordSense.Builder.Tests/NounVerbStackerTests.cs, test/WordSense.Builder.Tests/BuilderTests.cs, test/WordSense.Builder.Tests/CorpusTests.cs, test/WordSense.Builder.Tests/LexiconTests.cs, test/WordSense.Builder.Tests/LexiconImporterTests.cs, test/WordSense.Builder.Tests/WeightsTrainerTests.cs, test/WordSense.Builder.Tests/ChooserCorpusTests.cs, test/WordSense.Builder.Tests/ChooserTrainingTests.cs, test/WordSense.Builder.Tests/KernelFitTests.cs, test/WordSense.Builder.Tests/ThresholdsTests.cs, test/WordSense.Builder.Tests/RealCalibratorTests.cs, test/WordSense.Builder.Tests/RealSplitTests.cs, test/WordSense.Builder.Tests/SensePriorTests.cs, test/WordSense.Builder.Tests/TiersTests.cs, test/WordSense.Builder.Tests/EmbeddingCacheTests.cs, test/WordSense.Builder.Tests/FitCacheTests.cs, test/WordSense.Builder.Tests/ModelTrainerTests.cs, test/WordSense.Builder.Tests/EvaluatorTests.cs, test/WordSense.Builder.Tests/ModelTableTests.cs, test/WordSense.Builder.Tests/SenseEvaluatorTests.cs, test/WordSense.Builder.Tests/RunningTextEvaluatorTests.cs, test/WordSense.Builder.Tests/TenseEvaluatorTests.cs, test/WordSense.Builder.Tests/ChallengeSetFloorTests.cs, test/WordSense.Builder.Tests/SuiteFileTests.cs, test/WordSense.Builder.Tests/ShapeProbeTests.cs, test/WordSense.Builder.Tests/ShapeRowsTests.cs, test/WordSense.Builder.Tests/LeakageCheckTests.cs, test/WordSense.Builder.Tests/CoverageReportTests.cs, test/WordSense.Builder.Tests/HeteronymTests.cs, test/WordSense.Builder.Tests/AllWordsTests.cs, test/WordSense.Builder.Tests/Gold2Tests.cs, test/WordSense.Builder.Tests/ImageCompilerTests.cs, test/WordSense.Builder.Tests/FetchModelsTests.cs */
        comment designRef /* Design: docs/design/word-sense/word-sense-builder.md */
        comment verificationRef /* Verification: docs/verification/word-sense/word-sense-builder.md */
        comment reqRef /* Requirements: docs/reqstream/word-sense/word-sense-builder.yaml */
    }
}
