package WordSense {
    part def BasicClassifier {
        doc /* The classifier of the basic model: looks each word up in the lexicon in lower case and, for a word with several analyses, fuses part-of-speech posteriors and context cues (the scores of each cue table scaled by its reliability) into a probability for every analysis, weighs down the analyses whose lemma has the other case than the written word (a lower-case word against a capitalized lemma such as Polish, an isolated capitalized word inside a sentence against a lower-case lemma; a sentence-initial capital, a capitalized word next to another capitalized word, an upper-case or mixed-case word and the words of a title-case segment carry no such evidence), splits the probability of every verb slot that has both a past and a non-past analysis (put, cut, set, come, read) between them by the tense that the context says, read from the shared tense table of the basic model and never changing the probability of the slot, shifts the probability between the noun slot and the verb slot of a word that has both by the context, read from the shared noun/verb table of the basic model and keeping their total, the analyses of one lemma and part of speech (a slot) sharing the probability of the slot, selecting the best analysis of the most probable slot; it answers at the part of speech level with the probability of the slot as confidence (the sense level where the selected analysis has one sense), never at the group level, lists the only sense of an analysis whose lemma and part of speech have exactly one sense, and for an analysis that has two or more senses lists them ranked by the usage prior (the WordNet 3.0 tag count of each sense with add-k smoothing, k = 1, ties in inventory order) for the lemmas that no model scores, which is a statement about the lemma and never an answer: the level, the confidence, the sense id and the group id are those of the classifier without the ranking. */

        comment sourceRef /* Source: src/DemaConsulting.WordSense/BasicClassifier.cs, src/DemaConsulting.WordSense/UsagePrior.cs */
        comment testRef /* Test: test/DemaConsulting.WordSense.Tests/BasicClassifierTests.cs, test/DemaConsulting.WordSense.Tests/BasicClassifierUsagePriorTests.cs, test/DemaConsulting.WordSense.Tests/UsagePriorTests.cs */
        comment designRef /* Design: docs/design/word-sense/core/basic-classifier.md */
        comment verificationRef /* Verification: docs/verification/word-sense/core/basic-classifier.md */
        comment reqRef /* Requirements: docs/reqstream/word-sense/core/basic-classifier.yaml */
    }
}
