package WordSense {
    part def WordSenseContracts {
        doc /* The public contracts shared by every model package: the disposable model interface (the model owns the lifetime and classifies, ensuring its files lazily), the optional capability interface IDownloadableWordSenseModel (the ensure step with the download options, implemented only by models that have files), the composite FallbackWordSenseModel that answers each word with the result of a primary model where it scored senses and otherwise with the result of a fallback model (giving the equally likely variants of a slot of the primary result the proportions of the fallback, without changing the probability of any slot, and, for a primary weight below 1, combining the slot probabilities of both models as a weighted geometric mean where the primary result stays at the part-of-speech level, an answer at the sense or group level being left untouched; for a primary model that provides part-of-speech evidence, marked by the internal interface IPartOfSpeechEvidenceModel, reweighing the slot probabilities of a word of several parts of speech against the fallback as a weighted geometric mean at every level, an answer keeping its level while its slot stays the most probable and stepping down to the part of speech otherwise; for a primary model that also provides tense evidence, setting the share of the past analyses of a same-spelling verb to the weighted combination of the probability of past of the primary model and the past share of the fallback, TenseFusion) and forwards the ensure step to the members that have the capability, the download options, the typed exceptions (the abstract WordSenseException with ModelUnavailableException, ModelIntegrityException and DownloadConfigurationException), the answer values (classification result with its ranked analyses, each with its ranked senses; answer level; word details as one analysis and part of speech) and the sense and group records of the catalog, and the word key that names the meaning of every answer (ClassifyResult.Key, derived from the result alone, and the WordKey record that formats and parses it). */

        comment sourceRef /* Source: src/DemaConsulting.WordSense/IWordSenseModel.cs, src/DemaConsulting.WordSense/IDownloadableWordSenseModel.cs, src/DemaConsulting.WordSense/DownloadOptions.cs, src/DemaConsulting.WordSense/WordSenseException.cs, src/DemaConsulting.WordSense/ModelUnavailableException.cs, src/DemaConsulting.WordSense/ModelIntegrityException.cs, src/DemaConsulting.WordSense/DownloadConfigurationException.cs, src/DemaConsulting.WordSense/FallbackWordSenseModel.cs, src/DemaConsulting.WordSense/IPartOfSpeechEvidenceModel.cs, src/DemaConsulting.WordSense/TenseFusion.cs, src/DemaConsulting.WordSense/ClassifyResult.cs, src/DemaConsulting.WordSense/AnalysisCandidate.cs, src/DemaConsulting.WordSense/SenseCandidate.cs, src/DemaConsulting.WordSense/WordDetails.cs, src/DemaConsulting.WordSense/SenseInfo.cs, src/DemaConsulting.WordSense/SenseLevel.cs, src/DemaConsulting.WordSense/WordKey.cs */
        comment testRef /* Test: test/DemaConsulting.WordSense.Tests/ContractsTests.cs, test/DemaConsulting.WordSense.Tests/FallbackWordSenseModelTests.cs, test/DemaConsulting.WordSense.Tests/FallbackWordSenseModelEvidenceTests.cs, test/DemaConsulting.WordSense.Tests/FallbackWordSenseModelTenseTests.cs, test/DemaConsulting.WordSense.Tests/TenseFusionTests.cs, test/DemaConsulting.WordSense.Tests/WordSenseExceptionTests.cs, test/DemaConsulting.WordSense.Tests/WordKeyTests.cs, test/DemaConsulting.WordSense.Tests/KeyCompleteness.cs, test/DemaConsulting.WordSense.MiniLM.Tests/MiniLMKeyTests.cs, test/DemaConsulting.WordSense.BertBaseCased.Tests/BertBaseCasedKeyTests.cs */
        comment designRef /* Design: docs/design/word-sense/core/word-sense-contracts.md */
        comment verificationRef /* Verification: docs/verification/word-sense/core/word-sense-contracts.md */
        comment reqRef /* Requirements: docs/reqstream/word-sense/core/word-sense-contracts.yaml */
    }
}
